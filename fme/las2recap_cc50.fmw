FME workspace las2recap_cc50.fmw

Parameters:
- SourceDataset_LAS = E:\0_en_cours\2022_comines_warneton_armentieres\nuages\temp\*.laz   # Source ASPRS LAS File(s)
- DestDataset_RECAP = E:\0_en_cours\2022_comines_warneton_armentieres\nuages   # Destination ReCap Project Folder

Readers:
- LAS_1: LAS from $(SourceDataset_LAS) in EPSG:3950

Writers:
- RECAP_1: RECAP to $(DestDataset_RECAP) in EPSG:3950

ModuloCounter
    CNT_ATTR = _modulo_count
    DOMAIN = modcounter
    MOD = 10
    -> LAS (writer RECAP_1)

Bookmark: Reader Feature Types
LAS (reader LAS_1)
    -> ModuloCounter

Bookmark: Writer Feature Types
LAS (writer RECAP_1)
