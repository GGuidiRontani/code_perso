FME workspace dxf2dwg2018.fmw

Parameters:
- SourceDataset_ACAD = E:\0_en_cours\2022_armentieres_pres_hem\maillages\Mesh.dxf   # Source Autodesk AutoCAD DWG/DXF File(s)
- FEATURE_TYPES =
- DestDataset_ACAD = E:\0_en_cours\2022_armentieres_pres_hem\maillages\2018_armentieres_pres_hem_mnt_cc50.dwg   # Destination Autodesk AutoCAD DWG/DXF File

Readers:
- ACAD_1: ACAD from $(SourceDataset_ACAD) in EPSG:3950

Writers:
- ACAD_2: ACAD to $(DestDataset_ACAD) in EPSG:3950

Bookmark: Reader Feature Types
0 (reader ACAD_1)
    -> DYNAMIC (writer ACAD_2)

Bookmark: Writer Feature Types
DYNAMIC (writer ACAD_2)
