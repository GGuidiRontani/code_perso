FME workspace shapefile_fbx2acad.fmw

Parameters:
- DestDataset_ACAD = E:\0_en_cours\2022_armentieres_pres_hem\maillages\2018_armentieres_pres_hem_mnt_cc50.dwg   # Destination Autodesk AutoCAD DWG/DXF File
- SourceDataset_SHAPEFILE = E:\0_en_cours\2022_armentieres_pres_hem\sig\temp.shp   # Source Esri Shapefile(s)
- FEATURE_TYPES_2 =
- SourceDataset_FBX_3 = E:\0_en_cours\2022_armentieres_pres_hem\maillages\test.fbx   # Source FBX File(s)

Readers:
- SHAPEFILE_1: SHAPEFILE from $(SourceDataset_SHAPEFILE) in EPSG:3950
- FBX_2: FBX from $(SourceDataset_FBX_3) in EPSG:3950

Writers:
- ACAD_1: ACAD to $(DestDataset_ACAD) in EPSG:3950

test (reader FBX_2)
    -> Clipper [CLIPPER]
temp (reader SHAPEFILE_1)
    attributes: moche char(254)
    -> Clipper [CLIPPEE]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> DYNAMIC (writer ACAD_1)
DYNAMIC (writer ACAD_1)
